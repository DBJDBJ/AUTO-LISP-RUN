;
; remove.lsp DBJ 21.02.92
;
 (DEFUN C:REMEXTRA (/ Qj Q@ QQ Ql Q& Q1 Q# Q0 Q$ QO Q| Q% Q?j Qjj Q@j)
 (setq Q0 (GETVAR "ucsicon"))
 (SETVAR"ucsicon"0)
 (SETQ QO (GETVAR "cmdecho"))
 (SETVAR"cmdecho"0)
 (SETQ Q| (GETVAR "ucsfollow"))
 (SETVAR"ucsfollow"0)
 (SETQ Q$ 0)
 (SETQ Q% (- 0 1))
 (SETQ Q?j (LIST 45 92 124 47 45 92 124 47))
 (SETQ Qj (ENTNEXT))
 (SETQ Q@j 0)
 (COMMAND "ucs" "w")
 (WHILE Qj
 (SETQ Qj (ENTGET Qj))
 (IF (= Q% 7)
 (SETQ Q% 0)
 (SETQ Q% (+ Q% 1)))
 (IF (OR (= (CDR (ASSOC 0 Qj))"LINE") (= (CDR (ASSOC 0 Qj))"3DLINE"))
 (PROGN (SETQ Q@ (SSGET"c" (TRANS (CDR (ASSOC 10 Qj)) 
				  (CDR (ASSOC -1 Qj)) 1)
 (TRANS (CDR (ASSOC 11 Qj)) (CDR (ASSOC -1 Qj))1)))
 (IF (> (SSLENGTH Q@)1)
 (PROGN (SSDEL (CDR (ASSOC -1 Qj))Q@)
 (COMMAND"ucs""za" (TRANS (CDR (ASSOC 10 Qj)) (CDR (ASSOC -1 Qj))0)
 (TRANS (CDR (ASSOC 11 Qj)) (CDR (ASSOC -1 Qj))0))
 (SETQ Qjj (TRANS (CDR (ASSOC 11 Qj)) (CDR (ASSOC -1 Qj))1))
 (SETQ QQ 0)
 (REPEAT (SSLENGTH Q@)
 (SETQ Ql (ENTGET (SSNAME Q@ QQ)))
 (IF (OR (= (CDR (ASSOC 0 Qj))"LINE") (= (CDR (ASSOC 0 Qj))"3DLINE"))
 (PROGN (SETQ Q& (TRANS (CDR (ASSOC 10 Ql)) (CDR (ASSOC -1 Ql))1))
 (SETQ Q1 (TRANS (CDR (ASSOC 11 Ql)) (CDR (ASSOC -1 Ql))1))
 (IF (AND (= (RTOS (ABS (NTH 0 Q&))2 5)"0.00000")
        (= (RTOS (ABS (NTH 1 Q&))2 5)"0.00000")
        (= (RTOS (ABS (NTH 0 Q1))2 5)"0.00000")
        (= (RTOS (ABS (NTH 1 Q1))2 5)"0.00000"))
        (IF (AND (>= (NTH 2 Q&)0.0)
               (<= (NTH 2 Q&) (NTH 2 Qjj))
               (>= (NTH 2 Q1)0.0)
               (<= (NTH 2 Q1) (NTH 2 Qjj)))
               (PROGN (ENTDEL (CDR (ASSOC -1 Ql)))
 (SETQ Q$ (+ Q$ 1))
 (IF (= Q% 7)
 (SETQ Q% 0)
 (SETQ Q% (+ Q% 1)))
 (PROMPT (STRCAT"\r" (CHR (NTH Q% Q?j))" Removed lines = " (ITOA Q$)".  Overlapping lines replaced = " (ITOA Q@j))))
 (PROGN (SETQ QQj (MIN (NTH 2 Q&) (NTH 2 Q1)0.0))
 (SETQ Qlj (MAX (NTH 2 Q&) (NTH 2 Q1) (NTH 2 Qjj)))
 (COMMAND"line" (LIST 0.0 0.0 QQj) (LIST 0.0 0.0 Qlj)"")
 (ENTDEL (CDR (ASSOC -1 Ql)))
 (SETQ Q@j (+ Q@j 1))
 (PROMPT (STRCAT"\r" (CHR (NTH Q% Q?j))" Removed lines = " (ITOA Q$)".  Overlapping lines replaced = " (ITOA Q@j))))))))
 (SETQ QQ (+ QQ 1)))
 (COMMAND"ucs""w")))))
 (SETQ Qj (ENTNEXT (CDR (ASSOC -1 Qj)))))
 (REDRAW)
 (SETVAR"ucsicon"Q0)
 (SETVAR"cmdecho"QO)
 (SETVAR"ucsfollow"Q|)
 (PROMPT
  (STRCAT"\rRemoved lines = " (ITOA Q$)".  Overlapping lines replaced = " (ITOA Q@j)".""  Done."))
 (PRINC))
